Attribute VB_Name = "工作桌面"
Option Explicit

Public addinInterface As TableCatchCatiaLib.TableCatchCatiaDll

Sub CATMain()
    If addinInterface Is Nothing Then
        Set addinInterface = New TableCatchCatiaLib.TableCatchCatiaDll
    End If
    addinInterface.PLMStart
End Sub

Attribute VB_Name = "提交全部文件"
Option Explicit


Sub CATMain()
    If addinInterface Is Nothing Then
        Set addinInterface = New TableCatchCatiaLib.TableCatchCatiaDll
    End If
    addinInterface.PutInS
End Sub

Attribute VB_Name = "提交多层文件"
Option Explicit
 
Sub CATMain()
    If addinInterface Is Nothing Then
        Set addinInterface = New TableCatchCatiaLib.TableCatchCatiaDll
    End If
    addinInterface.PutInL
End Sub

Attribute VB_Name = "提交当前文件"
Option Explicit

Sub CATMain()
    If addinInterface Is Nothing Then
        Set addinInterface = New TableCatchCatiaLib.TableCatchCatiaDll
    End If
    addinInterface.PutIn
End Sub

Attribute VB_Name = "提取全部文件"
Option Explicit

Sub CATMain()
    If addinInterface Is Nothing Then
        Set addinInterface = New TableCatchCatiaLib.TableCatchCatiaDll
    End If
    addinInterface.CatchS
End Sub

Attribute VB_Name = "提取多层文件"
Option Explicit

Sub CATMain()
    If addinInterface Is Nothing Then
        Set addinInterface = New TableCatchCatiaLib.TableCatchCatiaDll
    End If
    addinInterface.CatchL
End Sub

Attribute VB_Name = "提取当前文件"
Option Explicit

Sub CATMain()
    If addinInterface Is Nothing Then
        Set addinInterface = New TableCatchCatiaLib.TableCatchCatiaDll
    End If
    addinInterface.Catch
End Sub

Attribute VB_Name = "检索修改"
Option Explicit

Sub CATMain()
    If addinInterface Is Nothing Then
        Set addinInterface = New TableCatchCatiaLib.TableCatchCatiaDll
    End If
    addinInterface.EditPart
End Sub

Attribute VB_Name = "添加子件"
Option Explicit

Sub CATMain()
    If addinInterface Is Nothing Then
        Set addinInterface = New TableCatchCatiaLib.TableCatchCatiaDll
    End If
    addinInterface.AddPart
End Sub

Attribute VB_Name = "编辑全部文件属性"
Option Explicit

Sub CATMain()
    If addinInterface Is Nothing Then
        Set addinInterface = New TableCatchCatiaLib.TableCatchCatiaDll
    End If
    addinInterface.EditS
End Sub

Attribute VB_Name = "编辑多层文件属性"
Option Explicit

Sub CATMain()
    If addinInterface Is Nothing Then
        Set addinInterface = New TableCatchCatiaLib.TableCatchCatiaDll
    End If
    addinInterface.EditL
End Sub

Attribute VB_Name = "编辑当前文件属性"
Option Explicit

Sub CATMain()
    If addinInterface Is Nothing Then
        Set addinInterface = New TableCatchCatiaLib.TableCatchCatiaDll
    End If
    addinInterface.Edit
End Sub
